-- ============================================================================
-- MibName   : JWS-MIRROR-MIB
-- FileName  : joyware-switch-mirror.mib
-- ============================================================================
JWS-MIRROR-MIB DEFINITIONS ::= BEGIN
    IMPORTS
        MODULE-IDENTITY, OBJECT-TYPE, Integer32                     FROM SNMPv2-SMI
        DisplayString                                               FROM SNMPv2-TC
        jwSwitch                                                    FROM JOYWARE-SMI;

jwsMirrorMib MODULE-IDENTITY
    LAST-UPDATED    "201603011200Z"
    ORGANIZATION    "Joyware Electronic Technology Co.,Ltd"
    CONTACT-INFO    "Postal: BlockA,Chang TorchHotel,No.259 Wensan Road,Hangzhou,Zhejiang 310012 China
                     E-mail: jw-snmp@joyware.com
                        Tel: 800-8571264 "
    DESCRIPTION     "This MIB module defines MIB objects which provide mirror
                     configurable information about the Joyware switch devices."
    -- revision history
    REVISION        "201603011200Z"
    DESCRIPTION     "Initial revision."
    ::= { jwSwitch 4 }

jwsMirrorConfigGroup  OBJECT IDENTIFIER ::= { jwsMirrorMib 1 }

-- ****************************************************************************
--                  jwsMirrorConfigGroup
-- ****************************************************************************
jwsMirrorDestinationPort OBJECT-TYPE
     SYNTAX      Integer32
     MAX-ACCESS  read-write
     STATUS      current
     DESCRIPTION
                 "Mirroring destination port, port mirroring mode is disable if
                  mirror destination port is null"
     ::= { jwsMirrorConfigGroup 1 }

jwsMirrorTable OBJECT-TYPE
     SYNTAX      SEQUENCE OF JwsMirrorEntry
     MAX-ACCESS  not-accessible
     STATUS      current
     DESCRIPTION
                 "This table provides mirror source ports configuration."
     ::= { jwsMirrorConfigGroup 2 }

jwsMirrorEntry OBJECT-TYPE
     SYNTAX      JwsMirrorEntry
     MAX-ACCESS  not-accessible
     STATUS      current
     DESCRIPTION
                 "Information about a table entry."
     INDEX       { jwsMirrorSourcePort }
     ::= { jwsMirrorTable 1 }

JwsMirrorEntry ::= SEQUENCE {
     jwsMirrorSourcePort              Integer32,
     jwsMirrorMode                    INTEGER
     }

jwsMirrorSourcePort OBJECT-TYPE
     SYNTAX      Integer32
     MAX-ACCESS  read-only
     STATUS      current
     DESCRIPTION
                 "Mirror source port."
     ::= { jwsMirrorEntry 1 }

jwsMirrorMode OBJECT-TYPE
     SYNTAX      INTEGER {
                 tx(1),
                 rx(2),
                 both(3),
                 disabled(4)
                 }
     MAX-ACCESS  read-write
     STATUS      current
     DESCRIPTION
                 "Mirroring mode"
     DEFVAL      { disabled }
     ::= { jwsMirrorEntry 2 }

END
