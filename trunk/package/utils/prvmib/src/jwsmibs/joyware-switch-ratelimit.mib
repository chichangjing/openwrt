-- ============================================================================
-- MibName   : JWS-RATE-LIMIT-MIB
-- FileName  : joyware-switch-ratelimit.mib
-- ============================================================================
JWS-RATE-LIMIT-MIB DEFINITIONS ::= BEGIN
    IMPORTS
        MODULE-IDENTITY, OBJECT-TYPE, Integer32                     FROM SNMPv2-SMI
        DisplayString                                               FROM SNMPv2-TC
        jwSwitch                                                    FROM JOYWARE-SMI
        JwsRateLimitTypeMask, JwsEnableValue                        FROM JWS-TC;

jwsRateLimitMib MODULE-IDENTITY
    LAST-UPDATED    "201603011200Z"
    ORGANIZATION    "Joyware Electronic Technology Co.,Ltd"
    CONTACT-INFO    "Postal: BlockA,Chang TorchHotel,No.259 Wensan Road,Hangzhou,Zhejiang 310012 China
                     E-mail: jw-snmp@joyware.com
                        Tel: 800-8571264 "
    DESCRIPTION     "This MIB module defines MIB objects which provide rate limit
                     configurable information about the Joyware switch devices."
    -- revision history
    REVISION        "201603011200Z"
    DESCRIPTION     "Initial revision."
    ::= { jwSwitch 3 }

jwsPriRateLimitGroup        OBJECT IDENTIFIER ::= { jwsRateLimitMib 1 }

-- ****************************************************************************
--                  jwsPriRateLimitGroup
-- ****************************************************************************

jwsPriRateLimitTable OBJECT-TYPE
    SYNTAX      SEQUENCE OF JwsPriRateLimitEntry
    MAX-ACCESS  not-accessible
    STATUS      current
    DESCRIPTION
        "A table of the switch's physical port rate control entries."
    ::= { jwsPriRateLimitGroup 1 }

jwsPriRateLimitEntry OBJECT-TYPE
    SYNTAX      JwsPriRateLimitEntry
    MAX-ACCESS  not-accessible
    STATUS      current
    DESCRIPTION
        "Switch's physical port rate control entry"
    INDEX       { jwsPriRateLimitPortIndex }
    ::= { jwsPriRateLimitTable 1 }

JwsPriRateLimitEntry ::= SEQUENCE {
    jwsPriRateLimitPortIndex                    Integer32,
    jwsPriRateLimitIngressBucket0Enable         JwsEnableValue,
    jwsPriRateLimitIngressBucket0TypeMask       JwsRateLimitTypeMask,
    jwsPriRateLimitIngressBucket0Rate           Integer32,
    jwsPriRateLimitIngressBucket1Enable         JwsEnableValue,
    jwsPriRateLimitIngressBucket1TypeMask       JwsRateLimitTypeMask,
    jwsPriRateLimitIngressBucket1Rate           Integer32,
    jwsPriRateLimitIngressBucket2Enable         JwsEnableValue,
    jwsPriRateLimitIngressBucket2TypeMask       JwsRateLimitTypeMask,
    jwsPriRateLimitIngressBucket2Rate           Integer32,
    jwsPriRateLimitIngressBucket3Enable         JwsEnableValue,
    jwsPriRateLimitIngressBucket3TypeMask       JwsRateLimitTypeMask,
    jwsPriRateLimitIngressBucket3Rate           Integer32,
    jwsPriRateLimitIngressBucket4Enable         JwsEnableValue,
    jwsPriRateLimitIngressBucket4TypeMask       JwsRateLimitTypeMask,
    jwsPriRateLimitIngressBucket4Rate           Integer32,
    jwsPriRateLimitEgressRateEnable             JwsEnableValue,
    jwsPriRateLimitEgressRate                   Integer32
    }

jwsPriRateLimitPortIndex OBJECT-TYPE
    SYNTAX      Integer32
    MAX-ACCESS  read-only
    STATUS      current
    DESCRIPTION
        "Port index."
    ::= { jwsPriRateLimitEntry 1 }

jwsPriRateLimitIngressBucket0Enable OBJECT-TYPE
    SYNTAX      JwsEnableValue
    MAX-ACCESS  read-write
    STATUS      current
    DESCRIPTION
        "Enable/disable egress rate limit feature for this bucket."
    ::= { jwsPriRateLimitEntry 2 }

jwsPriRateLimitIngressBucket0TypeMask OBJECT-TYPE
    SYNTAX      JwsRateLimitTypeMask
    MAX-ACCESS  read-write
    STATUS      current
    DESCRIPTION
        "Bucket type mask."
    ::= { jwsPriRateLimitEntry 3 }

jwsPriRateLimitIngressBucket0Rate OBJECT-TYPE
    SYNTAX      Integer32 (64..100000)
    MAX-ACCESS  read-write
    STATUS      current
    DESCRIPTION
        "Ingress rate value(Kbit per sec) for this bucket."
    ::= { jwsPriRateLimitEntry 4 }

jwsPriRateLimitIngressBucket1Enable OBJECT-TYPE
    SYNTAX      JwsEnableValue
    MAX-ACCESS  read-write
    STATUS      current
    DESCRIPTION
        "Enable/disable egress rate limit feature for this bucket."
    ::= { jwsPriRateLimitEntry 5 }

jwsPriRateLimitIngressBucket1TypeMask OBJECT-TYPE
    SYNTAX      JwsRateLimitTypeMask
    MAX-ACCESS  read-write
    STATUS      current
    DESCRIPTION
        "Bucket type mask."
    ::= { jwsPriRateLimitEntry 6 }

jwsPriRateLimitIngressBucket1Rate OBJECT-TYPE
    SYNTAX      Integer32 (64..100000)
    MAX-ACCESS  read-write
    STATUS      current
    DESCRIPTION
        "Ingress rate value(Kbit per sec) for this bucket."
    ::= { jwsPriRateLimitEntry 7 }

jwsPriRateLimitIngressBucket2Enable OBJECT-TYPE
    SYNTAX      JwsEnableValue
    MAX-ACCESS  read-write
    STATUS      current
    DESCRIPTION
        "Enable/disable egress rate limit feature for this bucket."
    ::= { jwsPriRateLimitEntry 8 }

jwsPriRateLimitIngressBucket2TypeMask OBJECT-TYPE
    SYNTAX      JwsRateLimitTypeMask
    MAX-ACCESS  read-write
    STATUS      current
    DESCRIPTION
        "Bucket type mask."
    ::= { jwsPriRateLimitEntry 9 }

jwsPriRateLimitIngressBucket2Rate OBJECT-TYPE
    SYNTAX      Integer32 (64..100000)
    MAX-ACCESS  read-write
    STATUS      current
    DESCRIPTION
        "Ingress rate value(Kbit per sec) for this bucket."
    ::= { jwsPriRateLimitEntry 10 }

jwsPriRateLimitIngressBucket3Enable OBJECT-TYPE
    SYNTAX      JwsEnableValue
    MAX-ACCESS  read-write
    STATUS      current
    DESCRIPTION
        "Enable/disable egress rate limit feature for this bucket."
    ::= { jwsPriRateLimitEntry 11 }

jwsPriRateLimitIngressBucket3TypeMask OBJECT-TYPE
    SYNTAX      JwsRateLimitTypeMask
    MAX-ACCESS  read-write
    STATUS      current
    DESCRIPTION
        "Bucket type mask."
    ::= { jwsPriRateLimitEntry 12 }

jwsPriRateLimitIngressBucket3Rate OBJECT-TYPE
    SYNTAX      Integer32 (64..100000)
    MAX-ACCESS  read-write
    STATUS      current
    DESCRIPTION
        "Ingress rate value(Kbit per sec) for this bucket."
    ::= { jwsPriRateLimitEntry 13 }

jwsPriRateLimitIngressBucket4Enable OBJECT-TYPE
    SYNTAX      JwsEnableValue
    MAX-ACCESS  read-write
    STATUS      current
    DESCRIPTION
        "Enable/disable egress rate limit feature for this bucket."
    ::= { jwsPriRateLimitEntry 14 }

jwsPriRateLimitIngressBucket4TypeMask OBJECT-TYPE
    SYNTAX      JwsRateLimitTypeMask
    MAX-ACCESS  read-write
    STATUS      current
    DESCRIPTION
        "Bucket type mask."
    ::= { jwsPriRateLimitEntry 15 }

jwsPriRateLimitIngressBucket4Rate OBJECT-TYPE
    SYNTAX      Integer32 (64..100000)
    MAX-ACCESS  read-write
    STATUS      current
    DESCRIPTION
        "Ingress rate value(Kbit per sec) for this bucket."
    ::= { jwsPriRateLimitEntry 16 }

jwsPriRateLimitEgressRateEnable OBJECT-TYPE
    SYNTAX      JwsEnableValue
    MAX-ACCESS  read-write
    STATUS      current
    DESCRIPTION
        "Enable/disable egress rate limit feature for this bucket."
    ::= { jwsPriRateLimitEntry 17 }

jwsPriRateLimitEgressRate OBJECT-TYPE
    SYNTAX      Integer32 (64..100000)
    MAX-ACCESS  read-write
    STATUS      current
    DESCRIPTION
        "Egress rate value(Kbit per sec) for this bucket."
    ::= { jwsPriRateLimitEntry 18 }

END
